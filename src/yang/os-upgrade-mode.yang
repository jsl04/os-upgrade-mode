module os-upgrade-mode {
  namespace "http://com/example/osupgrademode";
  prefix os-upgrade-mode;

  import ietf-inet-types {
    prefix inet;
  }
  import tailf-ncs {
    prefix ncs;
  }

  list os-upgrade-mode {
    key device;

    uses ncs:service-data;
    ncs:servicepoint "os-upgrade-mode";

    // may replace this with other ways of refering to the devices.
    leaf device {
      type leafref {
        path "/ncs:devices/ncs:device/ncs:name";
      }
    }

    // replace with your own stuff here
  }
}
